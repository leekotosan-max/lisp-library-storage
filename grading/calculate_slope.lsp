(defun c:calculate_slope ()
  (princ "Select first point: ")
  (setq p1 (getpoint))
  (princ "Select second point: ")
  (setq p2 (getpoint))
  (setq dx (- (car p2) (car p1)))
  (setq dy (- (cadr p2) (cadr p1)))
  (setq slope (* (/ dy dx) 100))
  (princ (strcat "\nSlope between points: " (rtos slope 2 2) "%"))
)
(princ)
