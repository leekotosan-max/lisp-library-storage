(defun c:grade_points ()
  (setq layer_name "GradingPoints")
  (setq pt_count 0)
  (vlax-for obj (vlax-invoke (vla-get-activedocument (vlax-get-acad-object)) 'ModelSpace)
    (if (= (vla-get-layer obj) layer_name)
      (setq pt_count (+ pt_count 1))
    )
  )
  (princ (strcat "Total points on " layer_name ": " (itoa pt_count)))
)
(princ)
